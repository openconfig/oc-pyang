module oc-linter-validate {

  yang-version "1";

  // namespace
  namespace "http://openconfig.net/yang/linter/validate";

  prefix "linter-validate";

  // import some basic types
  import openconfig-extensions { prefix oc-ext; }
  import ietf-yang-types { prefix "fish"; }

  // meta
  organization "OpenConfig working group";

  contact
    "OpenConfig working group
    www.openconfig.net";

  description
    "This module tests the OpenConfig linter.";

  oc-ext:openconfig-version "0.0.1a";

  revision 2016-02-29 {
    reference "leap-day";
  }

  feature FEATURE {
    description "a feature";
  }

  identity identitylowercase {
    description "An invalid identity: lower case";
  }

  identity IDENTITY-WITH-HYPHENS {
    description "An invalid identity: upper case with hyphens";
  }

  identity VALID_IDENTITY {
    description "A valid identity";
  }

  grouping linter-top {
    description
      "Grouping covering the linter";

    leaf misplaced-leaf {
      type string;
      description
        "This leaf is outside of a config or state container, and hence
        is invalid";
    }

    container config {
      description
        "Configuration parameters";
      uses linter_config;

    }

    container state {
      config false;
      description
        "State parameters";
      uses linter_config;
    }

    container multiple-config-containers {
      description
        "Multiple config containers";

      container config {
        description
          "Config one";
        container nested {
          description "Invalid container";
          container config {
            description "Second config container";

            leaf multiple-config-containers-leaf {
              type string;
              description "check";
            }
          }
        }
      }
    }

    container read-write-state {
      description "state container left r/w";

      container config {
        description "config";
        leaf read-write {
          type string;
          description "READ-WRITE leaf";
        }
      }

      container state {
        description "state";
        leaf read-only {
          type string;
          description "NOT READ ONLY leaf";
        }
      }
    }

    container bad-list-container {
      description
        "A surrounding list container that has other elements";

      container config {
        description "Invalid config container in list container";
      }

      container state {
        description "Invalid state container in list container";
      }

      list list {
        key "keyval";
        description "A list";

        leaf keyval {
          type leafref {
            path "../config/keyval";
          }
          description
            "Reference to key value";
        }

        container config {
          description
            "Config values";

          leaf keyval {
            type string;
            description
              "Key value";
          }
        }
      }
    }

    container styleguide-avoid {
      description
        "Elements to be avoided by the styleguide";

      container config {
        presence "some presence";
        description
          "Config elements";

        choice choice {
          description
            "A choice";
          case ONE {
            description
              "A case";
            leaf one {
              type string;
              description
                "A leaf";
            }
          }
        }
      }
    }
  }

  grouping linter_config {
    description
      "Top level config leaves";

    leaf invalid-enumeration {
      type enumeration {
        enum lowercase {
          description "Lower case naming";
        }
        enum UPPERCASE-HYPHEN {
          description "Includes hyphens";
        }
      }
      description
        "A leaf not matching rules relating to enums";
    }

    leaf feature-leaf {
      if-feature FEATURE;
      type string;
      description
        "An if-feature leaf";
    }

    leaf BAD_NAMING {
      type string;
      description
        "A badly named leaf";
    }

    leaf oknaming {
      type string;
      description
        "A leaf with a valid name";
    }

    leaf well-named {
      type string;
      description
        "A leaf with a valid name two";
    }
  }


  uses linter-top;

  container invalid-top-level {
    description
      "An invalid top-level container";
  }

}
