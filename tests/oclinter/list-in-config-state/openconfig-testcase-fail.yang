module openconfig-testcase-fail {
  prefix "oc-tc";
  namespace "http://openconfig.net/linter/testcase";

  import openconfig-extensions { prefix oc-ext; }

  description
    "Failure test case for a list being directly within a
    config or state container.";

  oc-ext:openconfig-version "0.0.1";

  revision 2016-09-28 {
    reference "0.0.1";
    description
      "Revision statement";
  }

  grouping testcase-config {
    list test-list {
      key "valid";

      leaf valid {
        type leafref {
          path "../config/valid";
        }
      }

      container config {
        leaf valid { type string; }
      }

      container state {
        config false;
        leaf valid { type string; }
      }

    }
  }

  grouping testcase-top {
    container config {
      uses testcase-config;
    }

    container state {
      config false;
      uses testcase-config;
    }
  }

  uses testcase-top;
}
