module openconfig-testcase-succeed {
  prefix "oc-tc";
  namespace "http://openconfig.net/linter/testcase";

  import openconfig-extensions { prefix oc-ext; }

  description
    "Success test case for a list being directly within a
    config or state container.";

  oc-ext:openconfig-version "0.0.1";

  revision 2016-09-28 {
    reference "0.0.1";
    description
      "Revision statement";
  }

  grouping testcase-config {
    // no-op
  }

  grouping testcase-top {
    container config {
      uses testcase-config;
    }

    container state {
      config false;
      uses testcase-config;
    }
  }

  uses testcase-top;
}
