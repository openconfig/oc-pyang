module openconfig-testcase-succeed {
  prefix "oc-tc";
  namespace "http://openconfig.net/linter/testcase";

  import openconfig-extensions { prefix oc-ext; }

  description
    "Success test case for a complicated case where the state container is
    defined in a grouping and the config container isn't";

  oc-ext:openconfig-version "0.0.1";

  revision 2016-09-28 {
    reference "0.0.1";
    description
      "Revision statement";
  }

  grouping test-config {
  }

  grouping test-grouping-common {
    leaf tleaf { type string; }
  }

  grouping test-grouping-state {
    container state {
      config false;
      uses test-grouping-common;
    }
  }

  grouping input-interface-state {
    description
      "State information of interface";
  }

  grouping test-group {
    container test-container {
      container config {
        uses test-grouping-common;
      }
      uses test-grouping-state;
    }
  }

  grouping foo-top {
    container test {
      container config {
        uses test-config;
      }
      container state {
        config false;
        uses test-config;
        uses input-interface-state;
      }
      uses test-group;
    }
  }

  uses foo-top;

}
