module openconfig-testcase-fail {
  prefix "oc-tc";
  namespace "http://openconfig.net/linter/testcase";

  import openconfig-extensions { prefix oc-ext; }

  description
    "Failure test case for missing applied config leaves where the state
    container doesn't exist.";

  oc-ext:openconfig-version "0.0.1";

  revision 2016-09-28 {
    reference "0.0.1";
    description
      "Revision statement";
  }

  grouping test-config {
    leaf tleaf { type string; }
  }

  grouping foo-top {
    container test {
      container config {
        uses test-config;
      }
    }
  }

  uses foo-top;

}
