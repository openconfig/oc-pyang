module openconfig-testcase-fail {
  prefix "oc-tc";
  namespace "http://openconfig.net/linter/testcase";

  import openconfig-extensions { prefix oc-ext; }

  description
    "Failure test case for description of identity in an
    OpenConfig model";

  contact
    "OpenConfig Working Group";

  organization
    "OpenConfig Working Group";

  oc-ext:openconfig-version "0.0.1";

  revision 2016-09-28 {
    reference "0.0.1";
    description
      "Revision statement";
  }

  identity FOO {
    base "ietf-if:interface-type";
  }

  identity BAR {
    base "ift:other";
  }
}
