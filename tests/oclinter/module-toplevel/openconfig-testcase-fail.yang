module openconfig-testcase-fail {
  prefix "oc-tc";
  namespace "http://openconfig.net/linter/testcase";

  import openconfig-extensions { prefix oc-ext; }

  description
    "Failure test case whereby there are a data tree
    elements defined at the top level";

  oc-ext:openconfig-version "0.0.1";

  revision 2016-09-28 {
    reference "0.0.1";
    description
      "Revision statement";
  }

  grouping test-config {
    leaf test {
      type string;
    }
  }

  container test {
    container config {
      uses test-config;
    }
    container state {
      config false;
      uses test-config;
    }
  }
}
