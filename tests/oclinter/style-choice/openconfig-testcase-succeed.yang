module openconfig-testcase-succeed {
  prefix "oc-tc";
  namespace "http://openconfig.net/linter/testcase";

  import openconfig-extensions { prefix oc-ext; }

  description
    "Success test case for avoiding use of choice";

  oc-ext:openconfig-version "0.0.1";

  revision 2016-09-28 {
    reference "0.0.1";
    description
      "Revision statement";
  }

  grouping test-config {
    leaf tleaf { type string; }
  }

  grouping test-state {
    leaf state-leaf { type int8; }
  }

  grouping test-state-counters {
    leaf counter { type int8; }
  }

  grouping foo-top {
    container test {
      container config {
        uses test-config;
      }
      container state {
        config false;
        uses test-config;
        uses test-state;

        container counters {
          uses test-state-counters;
        }
      }
    }
  }

  uses foo-top;

}
