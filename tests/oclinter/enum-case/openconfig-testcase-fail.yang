module openconfig-testcase-fail {
  prefix "oc-tc";
  namespace "http://openconfig.net/linter/testcase";

  import openconfig-extensions { prefix oc-ext; }

  description
    "Failure test case for case of enumeration in an
    OpenConfig model";

  oc-ext:openconfig-version "0.0.1";

  revision 2016-09-28 {
    reference "0.0.1";
    description
      "Revision statement";
  }

  grouping testcase-config {
    leaf enumeration {
      type enumeration {
        enum lowercase;
      }
    }
  }

  grouping testcase-top {
    container config {
      uses testcase-config;
    }

    container state {
      config false;
      uses testcase-config;
    }
  }

  uses testcase-top;
}
