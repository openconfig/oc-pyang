module openconfig-testcase-fail {
  prefix "oc-tc";
  namespace "http://openconfig.net/linter/testcase";

  import openconfig-extensions { prefix oc-ext; }

  description
    "Fail test case for a single config or state container within
    the path for an element";

  oc-ext:openconfig-version "0.0.1";

  revision 2016-09-28 {
    reference "0.0.1";
    description
      "Revision statement";
  }

  grouping test-config {
    leaf value { type string; }
  }

  grouping foo-top {
    container test {
      list test-list {
        key "value";

        leaf value {
          type leafref {
            path "../config/config/value";
          }
        }

        container config {
          container config {
            uses test-config;
          }
        }

        container state {
          config false;
          uses test-config;
        }
      }
    }
  }

  uses foo-top;

}
