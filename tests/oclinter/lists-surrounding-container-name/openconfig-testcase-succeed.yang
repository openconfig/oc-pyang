module openconfig-testcase-succeed {
  prefix "oc-tc";
  namespace "http://openconfig.net/linter/testcase";

  import openconfig-extensions { prefix oc-ext; }

  description
    "Success test case for a list being within a
    surrounding container that has the same name.";

  oc-ext:openconfig-version "0.0.1";

  revision 2016-09-28 {
    reference "0.0.1";
    description
      "Revision statement";
  }

  grouping list-config {
    leaf keyleaf { type string; }
  }

  grouping foo-top {
    container foos {
      list foo {
        key "keyleaf";

        leaf keyleaf {
          type leafref {
              path "../config/keyleaf";
          }
        }

        container config {
          uses list-config;
        }

        container state {
          config false;
          uses list-config;
        }
      }
    }
  }

  uses foo-top;
}
