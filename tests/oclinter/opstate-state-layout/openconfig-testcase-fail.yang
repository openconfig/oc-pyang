module openconfig-testcase-fail {
  prefix "oc-tc";
  namespace "http://openconfig.net/linter/testcase";

  import openconfig-extensions { prefix oc-ext; }

  description
    "Failure test case for invalid op-state layout";

  oc-ext:openconfig-version "0.0.1";

  revision 2016-09-28 {
    reference "0.0.1";
    description
      "Revision statement";
  }

  grouping test-config {
    leaf tleaf { type string; }
  }

  grouping test-state {
    leaf state-leaf { type int8; }
  }

  grouping foo-top {
    container test {
      container config {
        uses test-config;
      }
      container state {
        config false;
        container state {
          uses test-state;
        }
      }
    }
  }

  uses foo-top;

}
