module openconfig-testcase-fail {
  prefix "oc-tc";
  namespace "http://openconfig.net/linter/testcase";

  import openconfig-extensions { prefix oc-ext; }

  description
    "Failure test case for augments within a module.";

  oc-ext:openconfig-version "0.0.1";

  revision 2016-09-28 {
    reference "0.0.1";
    description
      "Revision statement";
  }

  grouping test-config {
    leaf target {
      type string;
    }
  }

  augment /test/config {
    leaf augmented {
      type string;
    }
  }

  augment /test/state {
    leaf augmented {
      type string;
    }
  }

  grouping foo-top {
    container test {
      container config {
        uses test-config;
      }
      container state {
        config false;
        uses test-config;
      }
    }
  }

  uses foo-top;

}
