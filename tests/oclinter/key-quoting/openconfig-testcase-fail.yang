module openconfig-testcase-fail {
  prefix "oc-tc";
  namespace "http://openconfig.net/linter/testcase";

  import openconfig-extensions { prefix oc-ext; }

  description
    "Failure testcase to check compliance with quoting
    the key of a list";

  oc-ext:openconfig-version "0.0.1";

  revision 2016-09-28 {
    reference "0.0.1";
    description
      "Revision statement";
  }

  grouping test-list-config {
    description
      "Test list config container";

    leaf test-key {
      type string;
      description
        "Test list key";
    }
  }

  grouping testcase-top {
    description
      "Top-level grouping";

    container test-container {
      list test-list {
        key test-key;

        leaf test-key {
          type leafref {
            path "../config/test-key";
          }
        }

        container config {
          description
            "test-list config";
          uses test-list-config;
        }

        container state {
          config false;
          description
            "test-list state";
          uses test-list-config;
        }
      }
    }
  }
}
