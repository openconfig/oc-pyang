module openconfig-testcase-succeed {
  prefix "oc-tc";
  namespace "http://openconfig.net/linter/testcase";

  import openconfig-extensions { prefix oc-ext; }

  description
    "Success test case for the key of a list being a leafref";

  oc-ext:openconfig-version "0.0.1";

  revision 2016-09-28 {
    reference "0.0.1";
    description
      "Revision statement";
  }

  grouping foo-top {
    container test {
      list test-list {
        config false;
        key "key";

        leaf key {
          type leafref {
            path "../state/key";
          }
        }

        container state {
          config false;
          leaf key { type string; }
        }
      }
    }
  }

  uses foo-top;

}
