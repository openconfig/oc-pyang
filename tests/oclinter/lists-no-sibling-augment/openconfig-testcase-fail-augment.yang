module openconfig-testcase-fail-augment {
  prefix "oc-tc2";
  namespace "http://openconfig.net/linter/testcase2";

  import openconfig-extensions { prefix oc-ext; }
  import openconfig-testcase-fail { prefix oc-tc; }

  description
    "Failure test case for a list having siblings.";

  oc-ext:openconfig-version "0.0.1";

  revision 2016-09-28 {
    reference "0.0.1";
    description
      "Revision statement";
  }

  grouping augment-top {
    container hello {
      container state {
        config false;
        leaf hello-leaf { type string; }
      }
    }
  }


  augment '/oc-tc:surrounding-container' {
    uses augment-top;
  }

}
