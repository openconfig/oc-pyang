module openconfig-testcase-fail {
  prefix "oc-tc";
  namespace "http://openconfig.net/linter/testcase";

  import openconfig-extensions { prefix oc-ext; }

  description
    "Failure test case for compression causing a clash
    in names -- clash between leaf and container.
    
    /config/clash will have the same name as /clash
    after compression.";

  oc-ext:openconfig-version "0.0.1";

  revision 2016-09-28 {
    reference "0.0.1";
    description
      "Revision statement";
  }

  grouping container-config {
    leaf a { type string; }
  }

  grouping clash-config {
    leaf clash { type string; }
  }

  grouping foo-top {

    container config {
      uses clash-config;
    }
    container state {
      config false;
      uses clash-config;
    }
    

    container clash {
      container config {
        uses container-config;
      }
      container state {
        config false;
        uses container-config;
      }
    }
  }

  uses foo-top;
}
