module openconfig-testcase-succeed {
  prefix "oc-tc";
  namespace "http://openconfig.net/linter/testcase";

  import openconfig-extensions { prefix oc-ext; }

  include openconfig-submodule-succeed;

  description
    "Success testcase to check compliance with quoting
    the key of a list";

  oc-ext:openconfig-version "0.0.1";

  revision 2016-09-28 {
    reference "0.0.1";
    description
      "Revision statement";
  }

  grouping empty-top { }
}
